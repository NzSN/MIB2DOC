--
-- defines MGSOFT-MGBEEP-MIB MIB for sample SNMP agent extension
--
-- Copyright (C) 1995, 2003 by MG-SOFT Corporation.
-- All rights reserved.
--
-- Comments to: <info@mg-soft.com>
-- Web URL: http://www.mg-soft.com/
--

         MGSOFT-MGBEEP-MIB DEFINITIONS ::= BEGIN

         IMPORTS
                mgSamples
                        FROM MGSOFT-SMI-V1
                TimeTicks,  Counter, IpAddress
                        FROM RFC1155-SMI
                OBJECT-TYPE
                        FROM RFC-1212
                DisplayString
                        FROM RFC1213-MIB;

          
         speaker OBJECT IDENTIFIER ::= { mgSamples 1 }

         speakerControl OBJECT-TYPE
             SYNTAX  INTEGER  {
                         on(1),
                         off(2)
                     }
             ACCESS  read-write
             STATUS  mandatory
             DESCRIPTION
                     "Current state of the speaker.
                      To enable testing the speaker set this varible
                      to on(1) and query speakerTest.
                      To disable testing the speaker set this varible
                      to off(2)"
             ::= { speaker 1 }

         speakerBeeps OBJECT-TYPE
             SYNTAX  INTEGER (1..10)
             ACCESS  read-write
             STATUS  mandatory
             DESCRIPTION
                     "How many beeps should be played on speakerTest query."
             ::= { speaker 2 }

         speakerTest OBJECT-TYPE
             SYNTAX  DisplayString
             ACCESS  read-only
             STATUS  mandatory
             DESCRIPTION
                     "When this variable is queried the speaker beeps
                      <speakerBeeps> times."
             ::= { speaker 3 }

         speakerBeepsCounter OBJECT-TYPE
             SYNTAX  Counter
             ACCESS  read-only
             STATUS  mandatory
             DESCRIPTION
                     "Counts how many times the speaker has beeped."
             ::= { speaker 4 }

         speakerUpTime OBJECT-TYPE
             SYNTAX  TimeTicks
             ACCESS  read-only
             STATUS  mandatory
             DESCRIPTION
                     "Time elapsed since the device startup."
             ::= { speaker 5 }


         speakerFreqTable OBJECT-TYPE
             SYNTAX  SEQUENCE OF SpeakerFreqEntry
             ACCESS  not-accessible
             STATUS  mandatory
             DESCRIPTION
                     "Table of the speaker frequency parameters."
             ::= { speaker 9 }

          speakerFreqEntry OBJECT-TYPE
              SYNTAX  SpeakerFreqEntry
              ACCESS  not-accessible
              STATUS  mandatory
              DESCRIPTION
                      "Speaker frequency parameters entry."
              INDEX   { speakerFreqIndex }
              ::= { speakerFreqTable 1 }

          SpeakerFreqEntry ::=
              SEQUENCE {
                              speakerFreqIndex
                      INTEGER,
                              speakerFreqDescr
                      DisplayString,
                              speakerFreqUpTime
                      TimeTicks
              }

          speakerFreqIndex OBJECT-TYPE
              SYNTAX  INTEGER (1..255)
              ACCESS  read-only
              STATUS  mandatory
              DESCRIPTION
                      "A unique value for each frequency."
              ::= { speakerFreqEntry 1 }

          speakerFreqDescr OBJECT-TYPE
              SYNTAX  DisplayString
              ACCESS  read-only
              STATUS  mandatory
              DESCRIPTION
                      "Frequency description."
              ::= { speakerFreqEntry 2 }

         speakerFreqUpTime OBJECT-TYPE
             SYNTAX  TimeTicks
             ACCESS  read-only
             STATUS  mandatory
             DESCRIPTION
                     "Time elapsed since entry startup."
             ::= { speakerFreqEntry 3 }


         speakerTrapMode OBJECT-TYPE
             SYNTAX  INTEGER (0..3)
             ACCESS  read-write
             STATUS  mandatory
             DESCRIPTION
                     "The following values are supported:

                        0 - disable sending traps.
                        1 - enable sending traps to managers registered at Microsoft's SNMP Agent under the
                            HKEY_LOCAL_MACHINE\System\CurrentControlSet\Services\SNMP\Parameters\TrapConfiguration
                            key in the sustem registry.
                        2 - enable sending traps to the manager specified
                            with the speakerTrapDestAddress OID."
             ::= { speaker 6 }

         speakerTrapDestAddress OBJECT-TYPE
             SYNTAX  IpAddress
             ACCESS  read-write
             STATUS  mandatory
             DESCRIPTION
                     "IP destination address for sending traps in
                      the <speakerTrapMode = 2> mode."
             ::= { speaker 7 }

         speakerTrapFrequency OBJECT-TYPE
             SYNTAX  INTEGER (0..100)
             ACCESS  read-write
             STATUS  mandatory
             DESCRIPTION
                     "Number of beeps (speakerTest queries) before the
                      trap is sent to the specified manager(s)."
             ::= { speaker 8 }

         END
